TEST-MIB DEFINITIONS ::= BEGIN

IMPORTS
    OBJECT-TYPE, Integer32, MODULE-IDENTITY FROM SNMPv2-SMI;

testMIB MODULE-IDENTITY
    LAST-UPDATED "202404270000Z"
    ORGANIZATION "Your Organization"
    CONTACT-INFO "your.email@example.com"
    DESCRIPTION "Test MIB for testing SNMP SET commands"
    ::= { 1 3 6 1 4 1 12345 }

testObject OBJECT-TYPE
    SYNTAX      INTEGER (0..100)
    MAX-ACCESS  read-write
    STATUS      current
    DESCRIPTION "A test object to modify via SNMP"
    ::= { testMIB 1 }

END
